(defun C:NAZIH ()

   (setvar "cmdecho" 0)
   (setq clay (getvar "clayer"))
   (initget 1)
   (setq DAT-F (getfiled "Data File Name" "c:/" "*" 8))
   (setq SSDF (open DAT-F "r"))
   (SS));END defun
(prompt "\n**TYPE 'EHAB'TO DRAW A PROFLE FOR A SEWER**\n")(princ)
;***********Main Program*******************
(defun SS ()

   (setvar "orthomode" 1)
   (command "elev" "0.0" "0.0")
   (command "osnap" "int")
   (command "ucs" "w")
   (setq nam (read-line SSDF))
   (setq test_nam (strcat "\n*" "Do you want to draw profile for **" nam "** <Y>/N :"))
    (initget (+ 2 4) "Yes No")
   (if (/= "Yes" (getkword test_nam)) (tst))
   (setq ysc 10.0
	 p0 (getpoint "\n>>> Pick lower left corner: ")
	 p00 (getpoint p0 "\n>>> Pick upper left corner: "));setq
    (initget 1)
   (setq datum (getreal "\n>>> Enter Datum Level: "))
;   (setq ysc (getreal "\n>>> Enter Vertical Scale: "))
   (setq Sstat 0)
   (setq p0 (list (+ (car p0) 10.0) (cadr p0)))
   (setvar "orthomode" 0)
   (command "osnap" "none")
   (command "layer" "n" "EN-P-CL" "L" "center" "EN-P-CL" "C" "2" "EN-P-CL" "")
   (command "layer" "n" "EN-P-MH" "C" "130" "EN-P-MH" "")
   (command "layer" "n" "EN-P-GL" "C" "150" "EN-P-GL" "")
   (command "layer" "n" "EN-P-IL" "C" "12" "EN-P-IL" "")
   (command "layer" "n" "EN-P-TXT" "C" "3" "EN-P-TXT" "")
   (command "style" "TXT100" "ROMANS" "2.5" "1" "0" "N" "N" "N")
(initget (+ 2 4) "Yes No")
 (if (/= "No" (getkword "\n>>> Do you want me to write the vertical scale <Yes>/No: "))
   (vl_sc))
   (command "layer" "s" clay "")
;----------------- PROFILE NAME ---------
(command "style" "ROMANT" "ROMANC" "5" "1" "0" "N" "N" "N")
(command "layer" "s" "EN-P-TXT" "")
   (command "text" "r" (list (- (car p0) 40) (+ (cadr p0) 30)) "0" nam)
   (command "style" "TXT100" "ROMANS" "2.5" "1" "0" "N" "N" "N")
   (command "ucs" "o" (list (car p0) (cadr p0)))
    (setq Pstat 0.0)
;--------OUTLET DATA No.,Dist. ,GL ,IL out,IL in ,DIAM---------
;                     ----------------------------------------------
   (setq n1 (read-line SSDF))
   (setq n1len (strlen n1) n1len (1+ n1len)
         n1coun 0 n1tes "")
(loop1)
   (setq AA1 (substr n1 n1ys n1lss))
(RD_DATA)
   (setq Xstat Pstat)
   (setq vv (substr n1 (+ 1 n1xs) 1))
   (if (/= (ascii vv) 44) (ss3))
   (if (= (ascii vv) 44) (ss2))
(loop1)
   (setq FF2 (substr n1 n1ys n1lss))
   (setq FF2 (atof  FF2))
(loop1)
   (setq FF1 (substr n1 n1ys n1lss))
   (setq FF1 (atof  FF1))
;**** MH Number
   (command "layer" "s" "EN-P-TXT" "")
   (command "text" "m" (list Pstat -7.5) "90" AA1)
;****** Distance -- Station
   (command "text" "m" (list Pstat -67.5) "90" (rtos BB1 2 1))
   (setq Sstat BB1)
   (setq p0p BB1)
;***** Ground Level
   (command "text" "m" (list Pstat -22.5) "90" (rtos CC1 2 2))
;***** Diameter
   (command "text" "m" (list (- Pstat 5) -99) "0" (rtos FF2 2 0))
;--------------DRAW 1st PIPE--------------
(setq IL1 (list (- Pstat 1.5) (* ysc (- DD1 datum))))
   (setq IL11 (list (+ Pstat 1.5) (* ysc (- DD1 datum))))
   (setq IL111 (list (+ Pstat 1.5) (* ysc (- EE1 datum))))
   (setq gl1 (list (- Pstat 0.75) (* ysc (- CC1 datum))))
   (setq gl11 (list (+ Pstat 0.75) (* ysc (- CC1 datum))))
   (setq glm (list Pstat (* ysc (- CC1 datum))))
   (setq BDIA (* ysc (/ FF2 1000)))
   (setq CDIA (* ysc (/ FF1 1000)))
   (command "layer" "s" "EN-P-IL" "")
   (command "line" (list (- (car IL1) 5) (cadr IL1)) IL1 "")
   (command "line" (list (car IL1) (+ (cadr IL1) BDIA)) (list (- (car IL1) 5) (+ (cadr IL1) BDIA)) "")
   (command "layer" "s" "EN-P-CL" "")
   (command "line" (list (car IL1) (+ (cadr IL1) (/ BDIA 2))) (list (- (car IL1) 5) (+ (cadr IL1) (/ BDIA 2))) "")
   (command "layer" "s" "EN-P-MH" "")
   (command "line" (list (car IL1) (+ (cadr IL1) BDIA)) gl1 gl11 (list (car IL111) (+ (cadr IL111) CDIA)) "")
   (command "line" IL111 IL11 IL1 "")
   (command "line" (list (car IL1) (- (cadr IL1) 0.5)) (list (car IL11) (- (cadr IL11) 0.5)) "")
   (command "layer" "s" "EN-P-CL" "")
   (command "line" (list (car glm) (+ 10 (cadr glm))) (list (car glm) -2) "")
   (command "line" (list Pstat -74) (list Pstat -105) "")
;----------------Next Manholes Data------------------
(setq zz 1)
   (setq n1 (read-line SSDF))
   (while (or (/= n1 "NEW") (/= n1 "END")) (s1s) (setq zz (1+ zz)))
   );DEFUN PROF
;---------------Small LISP-------------------
 (defun s1s ()
  
   (setq FF2 FF1)
   (setq Pgl gl11)
   (setq Pil IL111)
   (setq n1len (strlen n1)
         n1coun 1  n1tes "")
(loop1)
   (setq AA1 (substr n1 (- n1ys 1) (+ n1lss 1)))
(RD_DATA)
   (setq Sstat (+ Sstat BB1))
   (setq Pstat Sstat)
   (setq Xstat (- Pstat p0p))
  (setq vv (substr n1 (+ 1 n1xs) 1))
   (if (/= (ascii vv) 44) (ss3))
   (if (= (ascii vv) 44) (ss2))
(loop1)
   (setq FF1 (substr n1 n1ys n1lss))
   (setq FF1 (atof  FF1))
(command "layer" "s" "EN-P-TXT" "")
   (command "text" "m" (list Xstat -7.5) "90" AA1)
   (command "text" "m" (list (- Xstat (/ BB1 2)) -69) "0" (rtos BB1 2 2))
   (command "text" "m" (list Xstat -67.5) "90" (rtos Sstat 2 1))
;***** Ground Level
   (command "text" "m" (list Xstat -22.5) "90" (rtos CC1 2 2))
;***** Diameter
   (command "text" "m" (list (- Xstat (/ BB1 2)) -99) "0" (rtos FF2 2 0))
;***********<<<DRAW OUTLET PIPE >>>>>*********************
   (setq IL1 (list (- Xstat 1.5) (* ysc (- DD1 datum))))
   (setq IL11 (list (+ Xstat 1.5) (* ysc (- DD1 datum))))
   (setq IL111 (list (+ Xstat 1.5) (* ysc (- EE1 datum))))
   (setq gl1 (list (- Xstat 0.75) (* ysc (- CC1 datum))))
   (setq gl11 (list (+ Xstat 0.75) (* ysc (- CC1 datum))))
   (setq glm (list Xstat (* ysc (- CC1 datum))))
   (setq BDIA (* ysc (/ FF2 1000)))
   (setq CDIA (* ysc (/ FF1 1000)))
   (setq slope (* 100 (/ (- (cadr IL1) (cadr PIL)) BB1)))
   (command "layer" "s" "EN-P-TXT" "")
   (command "text" "m" (list (- Xstat (/ BB1 2)) -84) "0" (rtos slope 2 2))
   (command "layer" "s" "EN-P-IL" "")
   (command "line" PIL IL1 "")
   (command "line" (list (car IL1) (+ (cadr IL1) BDIA)) (list (car PIL) (+ (cadr PIL) BDIA)) "")
   (command "layer" "s" "EN-P-CL" "")
   (command "line" (list (car IL1) (+ (cadr IL1) (/ BDIA 2))) (list (car PIL) (+ (cadr PIL) (/ BDIA 2))) "")
   (command "layer" "s" "EN-P-GL" "")
   (command "line" Pgl gl1 "")
   (command "layer" "s" "EN-P-MH" "")
   (command "line" (list (car IL1) (+ (cadr IL1) BDIA)) gl1 gl11 (list (car IL111) (+ (cadr IL111) CDIA)) "")
   (command "line" IL111 IL11 IL1 "")
   (command "line" (list (car IL1) (- (cadr IL1) 0.5)) (list (car IL11) (- (cadr IL11) 0.5)) "")
   (command "layer" "s" "EN-P-CL" "")
   (command "line" (list (car glm) (+ 10 (cadr glm))) (list (car glm) -2) "")
   (command "line" (list Xstat -74) (list Xstat -105) "")
   (setq n1 (read-line SSDF))
   (if (= n1 "NEW") (SS))
   (if (= n1 "END") (quit)))
;************ MH without Drop******
(defun ss2 ()
 
  (setq EE1 DD1)
;   (setq Xst (- Xstat BB1))
   (command "layer" "s" "EN-P-TXT" "")
   (command "text" "m" (list Xstat -37.5) "90" (rtos DD1 2 2))
   (setq AB (- CC1 DD1))
   (command "text" "m" (list Xstat -52.5) "90" (rtos AB 2 2))
   (setq EE1 DD1
         n1coun (+ n1coun 1)))
;************ MH with Drop******
 (defun ss3 ()

(loop1)
   (setq EE1 (substr n1 n1ys n1lss))
   (setq EE1 (atof EE1))
   (command "layer" "s" "EN-P-TXT" "")
   (command "text" "m" (list (- Xstat 2) -37.5) "90" (rtos DD1 2 2))
   (command "text" "m" (list (+ Xstat 2) -37.5) "90" (rtos EE1 2 2))
   (setq AB (- CC1 DD1)
         BA (- CC1 EE1))
   (command "text" "m" (list (- Xstat 2) -52.5) "90" (rtos AB 2 2))
   (command "text" "m" (list (+ Xstat 2) -52.5) "90" (rtos BA 2 2)))
;*********** Test
(defun tst ()

  (setq nx (read-line SSDF))
  (setq nxx (substr nx 1 3))
  (if (= nxx "NEW") (ss))
  (if (= nxx "END") (quit))
  (TST))
;************** LOOP************
(defun loop1 ()

   (setq n1coun (1+ n1coun) n1ys n1coun)
   (while (and (< n1coun n1len)
               (/= (ascii (setq n2tes (substr n1 n1coun 1))) 44))
               (setq n1coun (1+ n1coun)))
   (setq n1xs n1coun)
   (setq n1lss (- n1xs n1ys)))
;*****************ERROR************
(defun *error* (msg)

   (command "layer" "s" clay "")
   (command "osnap" "none")
   (princ "\n>>> ERROR: ")
   (princ msg)
 (princ))
;SSSSSSSSSSSSSSSSSSSSSSSSSSSSSSSSSSSSSSSSSSSSSSSSS
(defun vl_sc ()
 (command "layer" "s" "EN-P-TXT" "")
 (setq x00 (+ (* ysc (fix (/ (- (cadr p00) (cadr p0)) ysc))) (cadr p0)))
 (command "text" "r" (list (- (car p0) 12.5) (+ (cadr p0) 0.8)) "0" (rtos datum 2 2))
 (command "line" (list (- (car p0) 11) (cadr p0)) (list (- (car p0) 11) x00) "")
 (command "line" (list (- (car p0) 9) (cadr p0)) (list (- (car p0) 9) x00) "")
 (setq cnt 1
       test (/ (- x00 (cadr p0)) ysc))
 (while (<= cnt (+ 1 test))
 (command "line" (list (- (car p0) 10.2) (+ (cadr p0) (* ysc cnt))) (list (- (car p0) 10.2) (+ (cadr p0) (* ysc (- cnt 1)))) "")
 (command "line" (list (- (car p0) 10.0) (+ (cadr p0) (* ysc cnt))) (list (- (car p0) 10.0) (+ (cadr p0) (* ysc (- cnt 1)))) "")
 (command "line" (list (- (car p0) 9.80) (+ (cadr p0) (* ysc cnt))) (list (- (car p0) 9.80) (+ (cadr p0) (* ysc (- cnt 1)))) "")
 (setq cnt (+ 2 cnt))) ;while
 (setq cnt 1
       test (/ (- x00 (cadr p0)) ysc))
 (while (<= cnt (+ 1 test))
 (command "line" (list (- (car p0) 9.00) (+ (cadr p0) (* ysc cnt))) (list (- (car p0) 11.0) (+ (cadr p0) (* ysc cnt))) "")
 (command "text" "r" (list (- (car p0) 12.5) (+ (cadr p0) (* ysc cnt))) "0" (rtos (+ datum cnt) 2 2))
 (setq cnt (+ 1 cnt))) ;while
 )
;[[[[[[[[[[]]]]]]]]]]]]]]]
(defun RD_DATA ()
(loop1)
   (setq BB1 (substr n1 n1ys n1lss))
   (setq BB1 (atof BB1))
(loop1)
   (setq CC1 (substr n1 n1ys n1lss))
   (setq CC1 (atof CC1))
(loop1)
   (setq DD1 (substr n1 n1ys n1lss))
   (setq DD1 (atof DD1))
 )
;XXXXXXXXXXXXXXXXXXXXXXXXXXXX
